module service-function {

  namespace "urn:cisco:params:xml:ns:yang:sfc-sf";

  prefix sfc-sf;

  import ietf-inet-types {
      prefix inet;
      revision-date 2010-09-24;
      }
  import service-locator {
      prefix sfc-sl;
      revision-date 2014-07-01;
      }
  import service-statistics {
      prefix sfc-ss;
      revision-date 2014-07-01;
      }
  import sfc-common {
      prefix sfc-common;
      }


  organization "Cisco Systems, Inc.";
  contact "Reinaldo Penno <repenno@cisco.com>";


  description
    "This module contains a collection of YANG definitions for
     managing service function.";

  revision 2014-07-01 {
    description
      "Changes based on Opendaylight Testing.";
  }

  grouping service-function-entry {
    description
      "This group bundles together all information related to a
       single service function";
    leaf name {
      type sfc-common:sf-name;
      description
          "The name of the service function.";
    }
    leaf tenant-id {
      type sfc-common:tenant-id;
      description
        "This SF was created for a specific tenant-id";
    }
    leaf type {
      type sfc-common:sft-type;
      mandatory true;
      description
        "Service Function Type from service-function-type yang
         model";
    }
    leaf rest-uri {
      type inet:uri;
      description "URI of REST based management";
    }
    leaf ip-mgmt-address {
      type inet:ip-address;
      description
        "The IP and port used to configure this service-function";
    }
    //TODO should not use "_" in yang names. This will be deprecated before it becomes an issue.
    leaf request_reclassification {
        status deprecated;
        type boolean;
        description "This leaf determines whether SF can request
          reclassification by the SFF";
      }
    leaf nsh-aware {
      status deprecated;
      type boolean;
      description "Whether this SF can process NSH headers";
    }

    list sf-data-plane-locator {
      key "name";
      description
        "A network data-plane locator";
      leaf name {
          type sfc-common:sf-data-plane-locator-name;
        description
          "A unique string that represents this
           data-plane-locator";
      }
      uses sfc-sl:data-plane-locator;
      leaf service-function-forwarder {
        type sfc-common:sff-name;
        description
          "The service function forwarder associated with this
           locator";
      }
    }

    leaf backup-sf {
        type sfc-common:sf-name;
        description
         "The name of backup service function name for the service function.";
    }
  }

  container service-functions {
    description
      "A function that is responsible for specific
      treatment of received packets.  A Service Function can act at
      various layers of a protocol stack (e.g., at the network layer
      or other OSI layers).  A Service Function can be a virtual
      element or be embedded in a physical network element.  One of
      multiple Service Functions can be embedded in the same network
      element.  Multiple occurrences of the Service Function can be
      enabled in the same administrative domain.

      One or more Service Functions can be involved in the delivery
      of added-value services.  A non-exhaustive list of Service
      Functions includes: firewalls, WAN and application
      acceleration, Deep Packet Inspection (DPI),a LI (Lawful
      Intercept) module, server load balancers, NAT44 [RFC3022],
      NAT64 [RFC6146], NPTv6 [RFC6296], HOST_ID injection, HTTP
      Header Enrichment functions, TCP optimizer, etc.

      An SF may be SFC encapsulation aware, that is it receives, and
      acts on information in the SFC encapsulation, or unaware in
      which case data forwarded to the service does not contain the
      SFC encapsulation.";

    list service-function {
      key "name";
      description
        "This list holds configuration data for all service functions
         in the domain";
      uses service-function-entry;
    }
  }

  container service-functions-state {
    config false;
    description
      "This container hold operational state for all service
       functions";
    list service-function-state {
      key "name";
      description
        "This list holds operational data for all service functions
         in the domain";
      leaf name {
        type sfc-common:sf-name;
        description
          "the name of the service function";
      }
      uses sfc-ss:service-statistics-group {
        description "Global Service Function statistics";
      }
      list sf-service-path {
        key "name";
        leaf name {
          type sfc-common:sfp-name;
          description
            "The name of the Service Path";
        }
        uses sfc-ss:service-statistics-group;
        description
        "A list of all service function paths that contain this
         service function";
      }

      leaf backup-sf-selection {
       type sfc-common:sf-name;
       description
       "The name of backup service function name for the service function.";
       }
    }
  }

  rpc delete-all-service-function {
  description
    "Deletes all service functions";
  }

  rpc put-service-function {
    description
      "Creates a service function";
    input {
      uses service-function-entry;
    }
  }
  rpc read-service-function {
    description
      "Reads a service function";
    input {
      leaf name {
        type string;
        mandatory true;
        description "The name of the service function.";
      }
    }
    output {
      uses service-function-entry;
    }
  }
  rpc delete-service-function {
    description
      "Deletes a service function";
    input {
      leaf name {
        type string;
        mandatory true;
        description "The name of the service function.";
      }
    }
  }
}
